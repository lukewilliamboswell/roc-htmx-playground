package EnquiryCRMModel {
    doc /* Authoritative as-built systems model for Enquiry CRM. */

    public import CRMArchitecture::*;
    public import CRMRequirements::*;
    public import CRMRiskAndControls::*;
    public import CRMVerification::*;
}
